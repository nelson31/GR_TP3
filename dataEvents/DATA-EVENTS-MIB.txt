DATA-EVENTS-MIB DEFINITIONS ::= BEGIN

IMPORTS
	enterprises,
	MODULE-IDENTITY,
	OBJECT-TYPE,
	Counter32
		FROM SNMPv2-SMI
	OBJECT-GROUP
		FROM SNMPv2-CONF;

dataEventsMIB MODULE-IDENTITY
	LAST-UPDATED "202102111629Z"	-- Feb 11, 2021, 4:29:00 PM
	ORGANIZATION ""
	CONTACT-INFO
		""
	DESCRIPTION
		"MIB usada para monitorização de datas de Eventos."
	REVISION "202102111629Z"	-- Feb 11, 2021, 4:29:00 PM
	DESCRIPTION
		"Initial version."
	-- 1.3.6.1.4.1.8888
	::= { enterprises 8888 }


dataEventsTotal OBJECT-TYPE
	SYNTAX  Counter32
	MAX-ACCESS read-only
	STATUS  current
	DESCRIPTION
		"Número total de Eventos presentes na MIB"
	-- 1.3.6.1.4.1.8888.1
	::= { dataEventsMIB 1 }


dataEventsTotalPast OBJECT-TYPE
	SYNTAX  Counter32
	MAX-ACCESS read-only
	STATUS  current
	DESCRIPTION
		"Número total de Eventos do passado presentes na MIB."
	-- 1.3.6.1.4.1.8888.2
	::= { dataEventsMIB 2 }


dataEventsTotalPresent OBJECT-TYPE
	SYNTAX  Counter32
	MAX-ACCESS read-only
	STATUS  current
	DESCRIPTION
		"Número total de Eventos do Presente presentes na MIB."
	-- 1.3.6.1.4.1.8888.3
	::= { dataEventsMIB 3 }


dataEventsTotalFuture OBJECT-TYPE
	SYNTAX  Counter32
	MAX-ACCESS read-only
	STATUS  current
	DESCRIPTION
		"Número total de Eventos do Futuro presentes na MIB."
	-- 1.3.6.1.4.1.8888.4
	::= { dataEventsMIB 4 }


dataEventsTable OBJECT-TYPE
	SYNTAX  SEQUENCE OF DataEventsEntry
	MAX-ACCESS not-accessible
	STATUS  current
	DESCRIPTION
		"Tabela de datas de Eventos identificadas por um Index."
	-- 1.3.6.1.4.1.8888.5
	::= { dataEventsMIB 5 }


dataEventsEntry OBJECT-TYPE
	SYNTAX  DataEventsEntry
	MAX-ACCESS not-accessible
	STATUS  current
	DESCRIPTION
		"Uma entrada/linha para a tabela de datas de eventos. A chave para a tabela é um indice que identifica cada data de um evento."
	INDEX {
		dataEventsIndex }
	-- 1.3.6.1.4.1.8888.5.1
	::= { dataEventsTable 1 }


DataEventsEntry ::= SEQUENCE {

	dataEventsIndex             Counter32,
	dataEventsIdent             OCTET STRING,
	dataEventsMsg               OCTET STRING,
	dataEventsTimeYears         INTEGER,
	dataEventsTimeMonths        INTEGER,
	dataEventsTimeWeeks         INTEGER,
	dataEventsTimeDays          INTEGER,
	dataEventsTimeHours         INTEGER,
	dataEventsTimeMinutes       INTEGER,
	dataEventsTimeDeleteYears   INTEGER,
	dataEventsTimeDeleteMonths  INTEGER,
	dataEventsTimeDeleteWeeks   INTEGER,
	dataEventsTimeDeleteDays    INTEGER,
	dataEventsTimeDeleteHours   INTEGER,
	dataEventsTimeDeleteMinutes INTEGER }


dataEventsIndex OBJECT-TYPE
	SYNTAX  Counter32
	MAX-ACCESS read-only
	STATUS  current
	DESCRIPTION
		"Indice identificador de uma data de Evento."
	-- 1.3.6.1.4.1.8888.5.1.1
	::= { dataEventsEntry 1 }


dataEventsIdent OBJECT-TYPE
	SYNTAX  OCTET STRING
	MAX-ACCESS read-only
	STATUS  current
	DESCRIPTION
		"Objeto que identifica o evento"
	-- 1.3.6.1.4.1.8888.5.1.2
	::= { dataEventsEntry 2 }


dataEventsMsg OBJECT-TYPE
	SYNTAX  OCTET STRING
	MAX-ACCESS read-only
	STATUS  current
	DESCRIPTION
		"Objeto que guarda a mensagem a apresentar mediante o centexto ser passado, presente ou futuro."
	-- 1.3.6.1.4.1.8888.5.1.3
	::= { dataEventsEntry 3 }


dataEventsTimeYears OBJECT-TYPE
	SYNTAX  INTEGER
	UNITS "anos"
	MAX-ACCESS read-only
	STATUS  current
	DESCRIPTION
		"Objeto que guarda o número de anos que faltam/passaram para/desde o evento."
	-- 1.3.6.1.4.1.8888.5.1.4
	::= { dataEventsEntry 4 }


dataEventsTimeMonths OBJECT-TYPE
	SYNTAX  INTEGER
	UNITS "meses"
	MAX-ACCESS read-only
	STATUS  current
	DESCRIPTION
		"Objetos que guarda o número de meses que faltam/passaram para/desde o evento."
	-- 1.3.6.1.4.1.8888.5.1.5
	::= { dataEventsEntry 5 }


dataEventsTimeWeeks OBJECT-TYPE
	SYNTAX  INTEGER
	UNITS "semanas"
	MAX-ACCESS read-only
	STATUS  current
	DESCRIPTION
		"Objeto que guarda o número de semanas que faltam/passaram para/desde o evento"
	-- 1.3.6.1.4.1.8888.5.1.6
	::= { dataEventsEntry 6 }


dataEventsTimeDays OBJECT-TYPE
	SYNTAX  INTEGER
	UNITS "dias"
	MAX-ACCESS read-only
	STATUS  current
	DESCRIPTION
		"Objeto que guarda o número de dias que faltam/passaram para/desde o evento"
	-- 1.3.6.1.4.1.8888.5.1.7
	::= { dataEventsEntry 7 }


dataEventsTimeHours OBJECT-TYPE
	SYNTAX  INTEGER
	UNITS "horas"
	MAX-ACCESS read-only
	STATUS  current
	DESCRIPTION
		"Objeto que guarda o número de horas que faltam/passaram para/desde o evento"
	-- 1.3.6.1.4.1.8888.5.1.8
	::= { dataEventsEntry 8 }


dataEventsTimeMinutes OBJECT-TYPE
	SYNTAX  INTEGER
	UNITS "minutos"
	MAX-ACCESS read-only
	STATUS  current
	DESCRIPTION
		"Objeto que guarda o número de minutos que faltam/passaram para/desde o evento."
	-- 1.3.6.1.4.1.8888.5.1.9
	::= { dataEventsEntry 9 }


dataEventsTimeDeleteYears OBJECT-TYPE
	SYNTAX  INTEGER
	UNITS "anos"
	MAX-ACCESS read-only
	STATUS  current
	DESCRIPTION
		"Objeto que guarda o número de anos que faltam para remover o evento da mib"
	-- 1.3.6.1.4.1.8888.5.1.10
	::= { dataEventsEntry 10 }


dataEventsTimeDeleteMonths OBJECT-TYPE
	SYNTAX  INTEGER
	UNITS "meses"
	MAX-ACCESS read-only
	STATUS  current
	DESCRIPTION
		"Objeto que gaurda o número de meses que faltam para remover o evento da mib"
	-- 1.3.6.1.4.1.8888.5.1.11
	::= { dataEventsEntry 11 }


dataEventsTimeDeleteWeeks OBJECT-TYPE
	SYNTAX  INTEGER
	UNITS "semanas"
	MAX-ACCESS read-only
	STATUS  current
	DESCRIPTION
		"Objeto que guarda o número de semanas que faltam para apagar o evento da mib"
	-- 1.3.6.1.4.1.8888.5.1.12
	::= { dataEventsEntry 12 }


dataEventsTimeDeleteDays OBJECT-TYPE
	SYNTAX  INTEGER
	UNITS "dias"
	MAX-ACCESS read-only
	STATUS  current
	DESCRIPTION
		"Objeto que guarda o número de dias que faltam para apagar o evento da mib"
	-- 1.3.6.1.4.1.8888.5.1.13
	::= { dataEventsEntry 13 }


dataEventsTimeDeleteHours OBJECT-TYPE
	SYNTAX  INTEGER
	UNITS "horas"
	MAX-ACCESS read-only
	STATUS  current
	DESCRIPTION
		"Objeto que gaurda o número de horas que faltam para apagar o evento da mib"
	-- 1.3.6.1.4.1.8888.5.1.14
	::= { dataEventsEntry 14 }


dataEventsTimeDeleteMinutes OBJECT-TYPE
	SYNTAX  INTEGER
	UNITS "minutos"
	MAX-ACCESS read-only
	STATUS  current
	DESCRIPTION
		"Objeto que guarda o número de minutos que faltam para apagar o evento da mib"
	-- 1.3.6.1.4.1.8888.5.1.15
	::= { dataEventsEntry 15 }


-- Conformance
--

dataEventsMIBConf OBJECT IDENTIFIER 
	-- 1.3.6.1.4.1.8888.6
	::= { dataEventsMIB 6 }

-- Groups
--

dataEventsMIBGroups OBJECT IDENTIFIER 
	-- 1.3.6.1.4.1.8888.6.1
	::= { dataEventsMIBConf 1 }

-- Compliances
--

dataEventsMIBCompliances OBJECT IDENTIFIER 
	-- 1.3.6.1.4.1.8888.6.2
	::= { dataEventsMIBConf 2 }

dataEventsMIBBasicGroup OBJECT-GROUP
	OBJECTS {
		dataEventsTotal,
		dataEventsTotalPast,
		dataEventsTotalPresent,
		dataEventsTotalFuture,
		dataEventsTimeYears,
		dataEventsTimeMonths,
		dataEventsTimeWeeks,
		dataEventsTimeDays,
		dataEventsTimeHours,
		dataEventsTimeMinutes,
		dataEventsTimeDeleteYears,
		dataEventsTimeDeleteMonths,
		dataEventsTimeDeleteWeeks,
		dataEventsTimeDeleteDays,
		dataEventsTimeDeleteHours,
		dataEventsTimeDeleteMinutes,
		dataEventsMsg,
		dataEventsIndex,
		dataEventsIdent }
	STATUS  current
	DESCRIPTION
		"Basic objects."
	-- 1.3.6.1.4.1.8888.6.1.1
	::= { dataEventsMIBGroups 1 }

END
